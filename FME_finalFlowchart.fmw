FME workspace FME_finalFlowchart.fmw

Parameters:
- DestDataset_GEODATABASE_FILE = $(FME_MF_DIR)3D data and DTM - Karlskrona\test-outputs.gdb   # File Geodatabase
- SourceDataset_FILEGDB = $(FME_MF_DIR)3D data and DTM - Karlskrona\three_buildings.gdb   # File Geodatabase
- SourceDataset_FILEGDB_15 = $(FME_MF_DIR)3D data and DTM - Karlskrona\three_buildings.gdb   # File Geodatabase
- SourceDataset_FILEGDB_11 = $(FME_MF_DIR)3D data and DTM - Karlskrona\more_buildings.gdb   # File Geodatabase
- DestDataset_FILEGDB = $(FME_MF_DIR)3D data and DTM - Karlskrona\more_buildings.gdb   # File Geodatabase
- SourceDataset_FILEGDB_13 = $(FME_MF_DIR)3D data and DTM - Karlskrona\neighborhood.gdb   # File Geodatabase
- SourceDataset_FILEGDB_10 = $(FME_MF_DIR)3D data and DTM - Karlskrona\neighborhood.gdb   # File Geodatabase
- DestDataset_GEODATABASE_FILE_2 = $(FME_MF_DIR)3D data and DTM - Karlskrona\visualsOutputs.gdb   # File Geodatabase
- DestDataset_GEODATABASE_FILE_3 = $(FME_MF_DIR)3D data and DTM - Karlskrona\neighborhood.gdb   # File Geodatabase
- SourceDataset_GEODATABASE_FILE_19 = $(FME_MF_DIR)3D data and DTM - Karlskrona\three_buildings.gdb   # File Geodatabase
- SourceDataset_GEODATABASE_FILE_17 = $(FME_MF_DIR)3D data and DTM - Karlskrona\three_buildings.gdb   # File Geodatabase
- SourceDataset_FILEGDB_12 = $(FME_MF_DIR)3D data and DTM - Karlskrona\three_buildings.gdb   # File Geodatabase
- SourceDataset_GEODATABASE_FILE_14 = $(FME_MF_DIR)3D data and DTM - Karlskrona\complexBuildings.gdb   # File Geodatabase
- SourceDataset_FILEGDB_14 = $(FME_MF_DIR)3D data and DTM - Karlskrona\complexBuildings.gdb   # File Geodatabase
- SourceDataset_FILEGDB_9 = $(FME_MF_DIR)3D data and DTM - Karlskrona\more_buildings.gdb   # File Geodatabase
- DestDataset_GEODATABASE_FILE_4 = $(FME_MF_DIR)3D data and DTM - Karlskrona\visualsOutputs.gdb   # File Geodatabase
- SourceDataset_GEODATABASE_FILE_10 = $(FME_MF_DIR)3D data and DTM - Karlskrona\three_buildings.gdb   # File Geodatabase
- SourceDataset_GEODATABASE_FILE_16 = $(FME_MF_DIR)3D data and DTM - Karlskrona\karlskronaTrosso.gdb   # File Geodatabase
- DestDataset_GEODATABASE_FILE_5 = $(FME_MF_DIR)3D data and DTM - Karlskrona\karlskronaTrosso.gdb   # File Geodatabase
- SourceDataset_GEODATABASE_FILE_RASTER_DATASET = $(FME_MF_DIR)3D data and DTM - Karlskrona\3D_Data_Karlskrona.gdb   # File Geodatabase

Readers:
- FILEGDB_1: FILEGDB from $(SourceDataset_FILEGDB)
- FILEGDB_2: FILEGDB from $(SourceDataset_FILEGDB_15)
- FILEGDB_3: FILEGDB from $(SourceDataset_FILEGDB_11)
- FILEGDB_4: FILEGDB from $(SourceDataset_FILEGDB_9)
- FILEGDB_5: FILEGDB from $(SourceDataset_FILEGDB_13)
- FILEGDB_6: FILEGDB from $(SourceDataset_FILEGDB_10)
- GEODATABASE_FILE_1: GEODATABASE_FILE from $(SourceDataset_GEODATABASE_FILE_10)
- GEODATABASE_FILE_2: GEODATABASE_FILE from $(SourceDataset_GEODATABASE_FILE_19)
- GEODATABASE_FILE_3: GEODATABASE_FILE from $(SourceDataset_GEODATABASE_FILE_17)
- FILEGDB_7: FILEGDB from $(SourceDataset_FILEGDB_12)
- GEODATABASE_FILE_4: GEODATABASE_FILE from $(SourceDataset_GEODATABASE_FILE_14)
- FILEGDB_8: FILEGDB from $(SourceDataset_FILEGDB_14)
- GEODATABASE_FILE_5: GEODATABASE_FILE from $(SourceDataset_GEODATABASE_FILE_16)
- GEODATABASE_FILE_RASTER_DATASET_1: GEODATABASE_FILE_RASTER_DATASET from $(SourceDataset_GEODATABASE_FILE_RASTER_DATASET)

Writers:
- GEODATABASE_FILE_7: GEODATABASE_FILE to $(DestDataset_GEODATABASE_FILE)
- FILEGDB_9: FILEGDB to $(DestDataset_FILEGDB)
- GEODATABASE_FILE_8: GEODATABASE_FILE to $(DestDataset_GEODATABASE_FILE_2)
- GEODATABASE_FILE_9: GEODATABASE_FILE to $(DestDataset_GEODATABASE_FILE_3)
- GEODATABASE_FILE_10: GEODATABASE_FILE to $(DestDataset_GEODATABASE_FILE_4)
- GEODATABASE_FILE_11: GEODATABASE_FILE to $(DestDataset_GEODATABASE_FILE_5)

trosso (reader GEODATABASE_FILE_5)
    attributes: OBJECTID integer, BLDGHEIGHT float, EAVEHEIGHT float, ROOFFORM char(255), BuildingFID char(255), BASEELEV float, ROOFDIR smallint, RoofDirAdjust smallint, RMSE float, OriginalOID integer, ACCURACYHEIGHT double, ACCURACYPLAN double, ALTITUDE smallint, BALSTATUS smallint, ADDRESS char(255), AFFECTEDBY integer, BELONGSTO integer, BUILDINGSID char(38), BUILDINGNAMETYPE integer, BUILDINGREMARKTYPE integer, ACTIVITYTYPE smallint, COMMENTARY char(2000), CONSTRUCTIONYEAR smallint, DTYPE char(20), EASEMENTBUILDING smallint, EXEMPTADDRESSING smallint, EXTENSIONYEAR smallint, EXTERNALID integer, FITTED smallint, HOUSENUMBER smallint,
      ISMAINBUILDING smallint, LIESON integer, MEASUREMETHOD smallint, MODIFICATIONDATE date, MODIFICATIONSIGN char(255), NAME char(255), NONFREEHOLDPROPERTY smallint, ONGROUND smallint, ORIGINHEIGHT smallint, ORIGINPLAN smallint, PLACENAMEID char(255), PURPOSE smallint, REGDATE date, REGSIGN char(255), SCALE integer, SYNCDATE date, SRSORIGINHEIGHT smallint, SRSORIGINPLAN smallint, STATUS smallint, STYPE smallint, SUPPLIER smallint, UNCERTAINUSE smallint, USEFULFLOORSPACE integer, AFFECTEDBYUUID char(36), BELONGSTOUUID char(36), LIESONUUID char(36), OVERGROUND smallint, ORIG_FID integer
    -> AttributeRemover
Note: Aggregate based on BuildinFID
Aggregator_4
    ACCUM_ATTRS_NAME = Use Attributes From One Feature
    AGGREGATE_TYPE = Homogeneous Collection (If Possible)
    GROUP_BY = BuildingFID
    MODE = Geometry - Assemble One Level
    SEP = ,
    AGGREGATE -> NSLOD_0_1_b (writer GEODATABASE_FILE_11)
Note: Set solid building to green
GeometryColorSetter_4
    ALPHA = 1
    FILL_COLOR = 0,1,0
    MODE = Fixed
    REC = Yes
    SIDE = Both
    COLORED -> NSLOD_2_2a (writer GEODATABASE_FILE_11)
Aggregator_3
    ACCUM_ATTRS_NAME = Merge Incoming Attributes
    AGGREGATE_TYPE = Homogeneous Collection (If Possible)
    GROUP_BY = OBJECTID
    MODE = Geometry - Assemble One Level
    SEP = ,
    AGGREGATE -> AttributeRounder_3
AttributeRounder_3
    PLACES = 4
    ROUND_TYPE = Nearest
    SRC_ATTRS = absHojdBotten absHojdTak bruttoarea takvinkel
    -> NS_building (writer GEODATABASE_FILE_11)

Bookmark: 1
Note: Remove all but relevant attributes
AttributeRemover
    REMOVE_ATTRS = ACCURACYHEIGHT,ACCURACYPLAN,ACTIVITYTYPE,ADDRESS,AFFECTEDBY,AFFECTEDBYUUID,ALTITUDE,BALSTATUS,BELONGSTO,BELONGSTOUUID,BLDGHEIGHT,BUILDINGNAMETYPE,BUILDINGREMARKTYPE,BUILDINGSID,COMMENTARY,CONSTRUCTIONYEAR,DTYPE,EASEMENTBUILDING,EXEMPTADDRESSING,EXTENSIONYEAR,EXTERNALID,FITTED,HOUSENUMBER,ISMAINBUILDING,LIESON,LIESONUUID,MEASUREMETHOD,MODIFICATIONDATE,MODIFICATIONSIGN,NAME,NONFREEHOLDPROPERTY,ONGROUND,ORIG_FID,OriginalOID,ORIGINHEIGHT,ORIGINPLAN,OVERGROUND,PLACENAMEID,PURPOSE,REGDATE,REGSIGN,RMSE,ROOFDIR,RoofDirAdjust,SCALE,SRSORIGINHEIGHT,SRSORIGINPLAN,STATUS,STYPE,SUPPLIER,SYNCDATE,UNCERTAINUSE,USEFULFLOORSPACE
    -> AttributeValueMapper
Note: Translate attributes for roof form to "taktyp"
AttributeValueMapper
    DIRECTION = Forward (Source To Destination)
    LUT = Flat,lågt lutande tak,Shed,pulpettak,Gable,sadeltak,Hip,valmat tak,Mansard,mansardtak,Dome,kupoltak
    SRC = ROOFFORM
    VAL_ATTR = taktyp
    -> BoundsExtractor_11
Note: Extracts highest and lowest z coordinates for each objects as absHojdBotten and absHojdTak
BoundsExtractor_11
    ZMAX = absHojdTak
    ZMIN = absHojdBotten
    -> GeometryPartExtractor
Note: Extracted: IFME_Face (this part) / Untouched: IFME_Mesh
GeometryPartExtractor
    GQUERY:
      for $geom in //geometry
      where $geom/@fme_geometry_type = 'IFMEFace'
      return number($geom/@fme_id)
    EXTRACTED -> SurfaceNormalExtractor
    UNTOUCHED -> GeometryPartExtractor_2
Note: Computes surface normals for each part
SurfaceNormalExtractor
    -> GeometryPropertyExtractor
Note: Retrieves surface normals from FMEs "Geometry Traits" for each part as an attribute
GeometryPropertyExtractor
    EXTRACTTYPE_PARAM = Traits
    PREFIX_EXTRACTED_TRAITS = No
    TRAIT_ATTR_LIST = surface_normal_x,No surface_normal_y,No surface_normal_z,No
    EXTRACTED -> BoundsExtractor_6

Bookmark: Meshes workflow
Note: Extracted: Mesh parts
GeometryPartExtractor_2
    GQUERY:
      for $geom in //geometry
      where $geom/@fme_geometry_type = 'Mesh Part'
      return number($geom/@fme_id)
    EXTRACTED -> MeasureRemover
Note: Remove vertex normal measures
MeasureRemover
    REMOVE_ALL = Yes
    -> GeometryValidator
Note: Compute new vertex normals
GeometryValidator
    PRESETS = Custom
    REPAIR = Yes
    RULES = "MISSING_VERTEX_NORMALS "
    SUMMARY = Detailed
    REPAIRED -> SurfaceNormalExtractor

Bookmark: 2
Note: Extracts highest and lowest z coordinates for each part
BoundsExtractor_6
    XMAX = _xmaxPart
    XMIN = _xminPart
    ZMAX = _zmaxPart
    ZMIN = _zminPart
    -> Tester_6
Note: Filter floor surfaces. zmaxPart = absHojdBotten
Tester_6
    BOOL_OP = OR
    COMPOSITE_TEST = 1
    TEST_CLAUSE = TEST @Value(_zmaxPart) = @Value(absHojdBotten)
    TEST_MODE = TEST
    PASSED -> Tester_12
    FAILED -> Tester_13
Note: Passed: surface normal z = -1 / Failed: Floors that are oriented wrongly
Tester_12
    BOOL_OP = OR
    COMPOSITE_TEST = 1
    TEST_CLAUSE = TEST @Value(surface_normal_z) = -1
    TEST_MODE = TEST
    PASSED -> Aggregator
    FAILED -> Orientor
Orientor
    FLIP_APPEARANCES_CHOICE = Yes
    KIND = REVERSE
    ORIENTED -> Aggregator
Note: Aggregates floor / parts, grouped by / "OBJECTID"
Aggregator
    ACCUM_ATTRS_NAME = Use Attributes From One Feature
    AGGREGATE_TYPE = Homogeneous Collection (If Possible)
    GROUP_BY = OBJECTID
    MODE = Geometry - Assemble One Level
    ORDERED = No
    SEP = ,
    AGGREGATE -> AreaCalculator
Note: Extracts wall features (passed). / and roof features (failed).
Tester_13
    BOOL_OP = OR
    COMPOSITE_TEST = 1
    TEST_CLAUSE = NUM_TEST @Value(surface_normal_z) RANGE (-0.11,0.11)
    TEST_MODE = NUM_TEST
    PASSED -> Aggregator_8
    FAILED -> Tester_14
Note: Passed: surface normal z > 0 (i.e.positive) / Failed: Roofs that are oriented wrongly
Tester_14
    BOOL_OP = OR
    COMPOSITE_TEST = 1
    TEST_CLAUSE = TEST @Value(surface_normal_z) > 0.000
    TEST_MODE = TEST
    PASSED -> Aggregator_2
    FAILED -> Orientor_2
Note: Flip wrongly oriented roof surfaces
Orientor_2
    FLIP_APPEARANCES_CHOICE = Yes
    KIND = REVERSE
    ORIENTED -> Aggregator_2
Note: Create a list out of surface normal z-values
Note: Aggregates roof / parts, grouped by / "OBJECTID"
Aggregator_2
    ACCUM_ATTRS_NAME = Use Attributes From One Feature
    AGGREGATE_TYPE = Homogeneous Collection (If Possible)
    GROUP_BY = OBJECTID
    LIST_ATTRS_TO_INCLUDE = surface_normal_z
    LIST_NAME = surface_normal_z
    MODE = Geometry - Assemble One Level
    ORDERED = No
    SEP = ,
    AGGREGATE -> ListDuplicateRemover

Bookmark: Final steps: Floors
Note: Calulates bruttoarea and saves results as attributes
AreaCalculator
    AREA_ATTR = bruttoarea
    AREA_TYPE = Plane Area
    MULT = 1
    -> GeometryColorSetter
Note: Create boundaryID
UUIDGenerator
    UUID_ATTR = boundaryID
    -> GeometryColorSetter_4
    -> Aggregator_3
    -> NSLOD_2_1_a (writer GEODATABASE_FILE_11)
    -> NSLOD_0_2_a (writer GEODATABASE_FILE_11)
    -> Aggregator_4

Bookmark: Floors
Note: Sets floor color to blue
GeometryColorSetter
    ALPHA = 1
    FILL_COLOR = 0,0.333333,1
    MODE = Fixed
    REC = Yes
    SIDE = Both
    COLORED -> UUIDGenerator

Bookmark: NS LOD 0.1b: Bottom
NSLOD_0_1_b (writer GEODATABASE_FILE_11)
    attributes: BuildingFID char(50)

Bookmark: Figure x: Takvinkel
Note: Remove duplicates in list
ListDuplicateRemover
    SRC_LIST = surface_normal_z{}.surface_normal_z
    -> ListElementCounter
Note: Count remaining values
ListElementCounter
    CNT_ATTR = _zcount
    LIST_NAME = surface_normal_z{}
    -> Tester_16
Note: If z-value count = 1
Tester_16
    BOOL_OP = OR
    COMPOSITE_TEST = 1
    TEST_CLAUSE = TEST @Value(_zcount) = 1
    TEST_MODE = TEST
    PASSED -> ExpressionEvaluator_2
    FAILED -> TestFilter_2
Note: Converting surface normals to roof pitch ange (in degrees), stored as attr. takvinkel
ExpressionEvaluator_2
    ACTION = Create New Attribute
    EXPRESSION = (@acos(@abs(@Value(surface_normal_z))))*180/@pi()
    VAL_ATTR = takvinkel
    -> TestFilter_2

Bookmark: Create absEAVE values
Note: If attr. EAVEHEIGHT and BASEELEV have valute, / Elseif EAVEHEIGHT has value but not BASEELEV / Else = missing EAVEHEIGHT values
TestFilter_2
    DEFAULT_VALUE = <UNFILTERED>
    TEST_LIST:
      "BOOL_OP,AND,COMPOSITE_TEST,""""""1 AND 2 AND 3"""""",TEST_CLAUSE,TEST EAVEHEIGHT NOT_ATTRIBUTE_VALUE_NULL ""
      TEST @Value(EAVEHEIGHT) > 0
      TEST BASEELEV NOT_ATTRIBUTE_VALUE_NULL """,EAVEHEIGHT and BASELEV ATTRIBUTE_HAS_A_VALUE
    EAVEHEIGHT and BASELEV ATTRIBUTE_HAS_A_VALUE -> AttributeCreator_4
    <UNFILTERED> -> BoundsExtractor_3
Note: Create attr. absEAVE (EAVEHEIGHT+BASEELEV)
AttributeCreator_4
    ATTR_TABLE = SET_TO absEAVE = @sum(@Value(EAVEHEIGHT),@Value(BASEELEV))
    -> Tester_5
    -> GeometryColorSetter_2
Note: Retrieve z-min roof as absEAVE
BoundsExtractor_3
    ZMIN = absEAVE
    -> Tester_5
    -> GeometryColorSetter_2

Bookmark: Figure x. Create flat roofs and raise to absEAVE --> roofs for LoD 0.2
Note: Passed: all but shed roof forms, failed: shed
Tester_5
    BOOL_OP = OR
    COMPOSITE_TEST = 1
    TEST_CLAUSE = TEST @Value(ROOFFORM) NOT_= Shed
    TEST_MODE = TEST
    PASSED -> 2DForcer
    FAILED -> Aggregator_6
Note: Forces a 2D geometry on the roof / features
2DForcer
    2D -> Dissolver_3
Note: Dissolve based on ObjectID. Without this action FaceReplacer does not work
Dissolver_3
    ACCUM_INPUT_ATTRS = Use Attributes From One Feature
    CLEANING_TOLERANCE = Automatic
    CONNECT_Z_MODE = First Wins
    DEAGGREGATE_INPUT = Yes
    GROUP_BY = OBJECTID
    AREA -> 3DForcer_4
Note: Forces a 3D geometry with / elevation values of absEAVE
3DForcer_4
    KEEPZVAL = No
    ZVALATTR = @Value(absEAVE)
    -> FaceReplacer_3
Note: Creates FME Face from a / polygon feature
FaceReplacer_3
    ANGULAR_TOLERANCE_CHOICE = Automatic
    THICKNESS_TOLERANCE_CHOICE = Automatic
    -> MeasureRemover_2
Note: Remove vertex normals (to have correct lighting)
MeasureRemover_2
    REMOVE_ALL = Yes
    -> GeometryValidator_2
Note: Vertex normals recalculated
GeometryValidator_2
    ISSUE_ATTR_NAME = _issues
    PRESETS = Custom
    REPAIR = Yes
    RULES = "MISSING_VERTEX_NORMALS "
    SUMMARY = Detailed
    REPAIRED -> Aggregator_6
Note: Aggregates roof parts for NS LoD 0.2 / Grouped by "OBJECTID".
Aggregator_6
    ACCUM_ATTRS_NAME = Use Attributes From One Feature
    AGGREGATE_TYPE = Homogeneous Collection (If Possible)
    GROUP_BY = OBJECTID
    MODE = Geometry - Assemble One Level
    ORDERED = No
    SEP = ,
    AGGREGATE -> GeometryColorSetter_3

Bookmark: Roof NS LoD 0.2
Note: Sets roof color to red
GeometryColorSetter_3
    ALPHA = 1
    FILL_COLOR = 1,0,0
    MODE = Fixed
    REC = Yes
    SIDE = Both
    COLORED -> UUIDGenerator_2
Note: Create boundaryID
UUIDGenerator_2
    UUID_ATTR = boundaryID
    -> NSLOD_0_2_a (writer GEODATABASE_FILE_11)

Bookmark: NS LOD 0.2:
NSLOD_0_2_a (writer GEODATABASE_FILE_11)
    attributes: boundaryID char(20), OBJECTID integer, begransningsyta char(20)

Bookmark: Roofs
Note: Sets roof color to red
GeometryColorSetter_2
    ALPHA = 1
    FILL_COLOR = 1,0,0
    MODE = Fixed
    REC = Yes
    SIDE = Both
    COLORED -> UUIDGenerator_3
Note: Create boundaryID
UUIDGenerator_3
    UUID_ATTR = boundaryID
    -> GeometryColorSetter_4
    -> Aggregator_3
    -> NSLOD_2_1_a (writer GEODATABASE_FILE_11)

Bookmark: NS LOD 2.1
NSLOD_2_1_a (writer GEODATABASE_FILE_11)
    attributes: boundaryID char(20), OBJECTID integer, begransningsyta char(20)

Bookmark: Walls
Note: Aggregates wall / parts / grouped by / "OBJECTID"
Aggregator_8
    ACCUM_ATTRS_NAME = Use Attributes From One Feature
    AGGREGATE_TYPE = Homogeneous Collection (If Possible)
    GROUP_BY = OBJECTID
    MODE = Geometry - Assemble One Level
    ORDERED = No
    SEP = ,
    AGGREGATE -> UUIDGenerator_4
Note: Create boundaryID
UUIDGenerator_4
    UUID_ATTR = boundaryID
    -> GeometryColorSetter_4
    -> Aggregator_3

Bookmark: NS LOD 2.2
NSLOD_2_2a (writer GEODATABASE_FILE_11)
    attributes: boundaryID char(20), OBJECTID integer, begransningsyta char(20)

Bookmark: NS buildingPart attributes
NS_building (writer GEODATABASE_FILE_11)
    attributes: BuildingFID char(20), OBJECTID integer, absHojdBotten float, absHojdTak float, bruttoarea float, taktyp char(30), takvinkel float

FME custom transformer SurfaceNormalExtractor
Calculates surface normal vectors on Faces from the average of the existing surface vertex normals. If no vertex normals exist, they will be generated by a GeometryValidator.
Normals will be stored as the following traits on each Face:
surface_normal_x
surface_normal_y
surface_normal_z
The SurfaceNormalExtractor will work on Composite and MultiSurfaces as well, with no need to de-aggregate. Meshes will be automatically converted to Composite Surfaces.
**Input**
Source features
**Output**
Output features with calculated surface normals

Input (input)
    -> GeometryCoercer_2
Note: Convert other surface types / to faced based surface
GeometryCoercer_2
    GQUERY:
      for $geom in //geometry
      where $geom/@fme_geometry_type = 'IFMEMesh'
      or $geom/@fme_geometry_type = 'IFMERectangleFace'
      or $geom/@fme_geometry_type = 'IFMETriangleFan'
      or $geom/@fme_geometry_type = 'IFMETriangleStrip'
      return number($geom/@fme_id)
    KIND = fme_composite_surface
    COERCED -> GeometryValidator
    UNTOUCHED -> GeometryValidator
Note: Generate vertex / normals if needed
GeometryValidator
    ISSUE_ATTR_NAME = _surface_normal_issues
    MISSING_VERTEX_NORMALS = MISSING_VERTEX_NORMALS
    PRESETS = Custom
    REPAIR = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    SUMMARY = None
    PASSED -> GeometryPropertySetter
    REPAIRED -> GeometryPropertySetter
Note: Create Face ids
GeometryPropertySetter
    CNT_ATTR = _surface_normal_id
    DOMAIN = _surface_normal_id
    GQUERY:
      for $geom in //geometry
      where $geom/@fme_geometry_type = 'IFMEFace'
      return number($geom/@fme_id)
    OVERWRITE_CHOICE = Yes
    SCOPE = Global
    SETTYPE_PARAM = Traits From Counter
    START = 0
    SET -> GeometryPartExtractor
    SET -> GeometryPropertySetter_UNTOUCHED_-__TraitMerger_REQUESTOR
    UNTOUCHED -> GeometryPropertySetter_UNTOUCHED_-__TraitMerger_REQUESTOR
    <REJECTED> -> Junction
GeometryPropertySetter_UNTOUCHED_-__TraitMerger_REQUESTOR: Junction
    -> TraitMerger [REQUESTOR]
Note: Extract Faces
GeometryPartExtractor
    EXTRACTTYPE_PARAM = Extract
    GQUERY:
      for $geom in //geometry
      where $geom/@fme_geometry_type = 'IFMEFace'
      return number($geom/@fme_id)
    PROCESSED -> GeometryPropertyExtractor
Note: Extract Face ids
GeometryPropertyExtractor
    EXTRACTTYPE_PARAM = Traits
    PREFIX_EXTRACTED_TRAITS = No
    TRAIT_ATTR_LIST = _surface_normal_id,No
    EXTRACTED -> GeometryCoercer
    UNTOUCHED -> Junction_2
Note: Coerce to polygon / for measure extraction
GeometryCoercer
    GQUERY:
      for $geom in //geometry
      where $geom/count(parent::geometry) = 0
      return number($geom/@fme_id)
    KIND = fme_polygon
    COERCED -> MeasureExtractor
Note: Extract normal measures
MeasureExtractor
    GEOM_TYPE = Whole Area
    MEASURE_LIST = fme_vertex_normal_x
    MEASURE_NAME = fme_vertex_normal_x
    -> MeasureExtractor_2
    <REJECTED> -> Junction_3
MeasureExtractor_2
    GEOM_TYPE = Whole Area
    MEASURE_LIST = fme_vertex_normal_y
    MEASURE_NAME = fme_vertex_normal_y
    -> MeasureExtractor_3
    <REJECTED> -> Junction_3
MeasureExtractor_3
    GEOM_TYPE = Whole Area
    MEASURE_LIST = fme_vertex_normal_z
    MEASURE_NAME = fme_vertex_normal_z
    -> ListSummer
    <REJECTED> -> Junction_3
Note: Sum normal measures
ListSummer
    RESULT = _normal_sum_x
    SRC_LIST = fme_vertex_normal_x{}
    -> ListSummer_2
ListSummer_2
    RESULT = _normal_sum_y
    SRC_LIST = fme_vertex_normal_y{}
    -> ListSummer_3
ListSummer_3
    RESULT = _normal_sum_z
    SRC_LIST = fme_vertex_normal_z{}
    -> ListElementCounter
Note: Count normal measures
ListElementCounter
    CNT_ATTR = _normal_count_x
    LIST_NAME = fme_vertex_normal_x{}
    -> ListElementCounter_2
ListElementCounter_2
    CNT_ATTR = _normal_count_y
    LIST_NAME = fme_vertex_normal_y{}
    -> ListElementCounter_3
ListElementCounter_3
    CNT_ATTR = _normal_count_z
    LIST_NAME = fme_vertex_normal_z{}
    -> AttributeCreator
Note: Calculate surface normal / from average of vertex / normals
AttributeCreator
    ATTR_TABLE:
      SET_TO surface_normal_x = @Evaluate(@Value(_normal_sum_x)/@Value(_normal_count_x))
      SET_TO surface_normal_y = @Evaluate(@Value(_normal_sum_y)/@Value(_normal_count_y))
      SET_TO surface_normal_z = @Evaluate(@Value(_normal_sum_z)/@Value(_normal_count_z))
    -> GeometryPropertySetter_2
Note: Set surface normal as traits
GeometryPropertySetter_2
    OVERWRITE_CHOICE = Yes
    REMOVE_ATTRIBUTE = No
    SETTYPE_PARAM = Traits From Attributes
    SRC_ATTRS = surface_normal_x _surface_normal_id surface_normal_z surface_normal_y
    SET -> AttributeRemover
    <REJECTED> -> Junction_4
Note: Remove uneeded attributes
AttributeRemover
    LIST_ATTRS = _surface_normal_issues{} fme_vertex_normal_x{} fme_vertex_normal_y{} fme_vertex_normal_z{}
    REMOVE_ATTRS = _normal_sum_x,surface_normal_x,_normal_sum_y,_normal_count_x,_normal_sum_z,_surface_normal_id,surface_normal_z,surface_normal_y
    -> AttributeKeeper_2
AttributeKeeper_2
    CREATE_BULK_MODE_FEATURES = No
    -> TraitMerger [SUPPLIER]
Note: Merge normal traits on / Faces by Face id
TraitMerger
    ATTR_ACCUM_MODE = Merge Supplier
    ATTR_CONFLICT_RES = Use Requestor
    COMPONENTS_TO_JOIN = _surface_normal_id;_surface_normal_id
    REQUESTOR_TYPE = Trait
    R_GQUERY:
      for $geom in //geometry
      where $geom/@fme_geometry_type = 'IFMEFace'
      return number($geom/@fme_id)
    SUPPLIER_TYPE = Trait
    S_GQUERY:
      for $geom in //geometry
      where $geom/count(parent::geometry) = 0
      return number($geom/@fme_id)
    RESULT -> GeometryPropertyRemover
    UNTOUCHED -> GeometryPropertyRemover
Note: Remove Face id
GeometryPropertyRemover
    REGEX_FILTER = _surface_normal_id
    REMOVETYPE_PARAM = Traits
    REMOVE_ALL = No
    REMOVED -> AttributeRemover_2
    UNTOUCHED -> AttributeRemover_2
Note: Remove uneeded attributes
AttributeRemover_2
    LIST_ATTRS = _surface_normal_issues{}
    -> Output (output)
Output (output)
Junction
    -> Junction_2
Junction_2
    -> Junction_3
Junction_3
    -> Junction_4
Junction_4
